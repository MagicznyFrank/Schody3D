import Part
import sys
import importWebGL
import logging
import traceback
from datetime import datetime
import os

log_file_path = '/schody3d/Schody3D/freecad.log'
logging.basicConfig(filename=log_file_path, level=logging.INFO)

def create_stairs(session_id, length, width, step_height, step_spacing, num_steps):
    try:
        doc_name = session_id
        logging.info("{} - Active document: {} - Using session_id as document name: {}".format(datetime.now(), App.ActiveDocument.Label if App.ActiveDocument else 'None', doc_name))

        App.newDocument(doc_name)
        doc = App.ActiveDocument

        substep_height = step_spacing + step_height
        base_vector = App.Vector(0, -width, 0)

        for i in range(1, int(num_steps) + 1):
            step = Part.makeBox(length, width, step_height)
            step.Placement.Base = base_vector + App.Vector(0, (i - 1) * width, (i - 1) * (step_spacing + step_height))
            doc.addObject("Part::Feature", f"Step{i}").Shape = step

            substep = Part.makeBox(length, 50, substep_height)
            substep.Placement.Base = step.Placement.Base + App.Vector(0, 0, -substep_height)
            doc.addObject("Part::Feature", f"Substep{i}").Shape = substep

        doc.recompute()
        logging.info("{} - Document created and stairs built successfully.".format(datetime.now()))
        return doc_name
    except Exception as e:
        logging.error("Error during stairs creation: {}".format(str(e)))
        traceback.print_exc()
        raise

def export_to_webgl(doc_name, num_steps):
    try:
        doc = App.ActiveDocument
        if doc:
            doc.saveAs(f"FreeCadProjects/{doc_name}.FCStd")
            objs = []
            for i in range(1, int(num_steps) + 1):
                step = doc.getObject(f"Step{i}")
                substep = doc.getObject(f"Substep{i}")
                if step:
                    objs.append(step)
                if substep:
                    objs.append(substep)

            export_path = f"FreeCadProjects/{doc_name}.html"
            importWebGL.export(objs, export_path)
            logging.info("Exported to WebGL successfully: {}".format(export_path))
        else:
            logging.error("Document not found for WebGL export.")
    except Exception as e:
        logging.error("Error during WebGL export: {}".format(str(e)))
        traceback.print_exc()

def get_stair_parameters():
    session_id = sys.argv[3]
    length = float(sys.argv[4])
    width = float(sys.argv[5])
    step_height = float(sys.argv[6])
    step_spacing = float(sys.argv[7])
    num_steps = int(sys.argv[8])

    doc_name = create_stairs(session_id, length, width, step_height, step_spacing, num_steps)
    export_to_webgl(doc_name, num_steps)

if __name__ == '__main__':
    get_stair_parameters()
    sys.exit(0)
